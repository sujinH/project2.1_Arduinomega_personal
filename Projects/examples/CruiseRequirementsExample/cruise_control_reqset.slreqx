# cruise_control_reqset

## R1: Max input throttle % (Functional)
The maximum input throttle is 00%

## R2: Cruise control speed operation range (Functional)
Cruise control has a minimum and maximum operating speed

### R2.1: Minimum vehicle speed (Functional)
The speed of the vehicle must be at least 40km/h for the cruise control system to engage
