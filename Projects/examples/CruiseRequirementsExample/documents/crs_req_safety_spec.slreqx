# crs_req_safety_spec

## #1: Maximum Throttle Value (Functional)
Maximum value for the throttle should be equal to or less than 100.

## #2: Minimum Throttle Value (Functional)
Minimum Throttle value must not be less than 0.

## #3: Maximum Target Speed (Functional)
Maximum value for target speed should be equal to or less than 100.

## #4: Minimum Target Speed (Functional)
Minimum target speed must not be less than 40.
